import FreeCAD, Part
doc = FreeCAD.ActiveDocument or FreeCAD.newDocument("FloatFrame")
groups = {}
groups.setdefault("chassis_rail", []).append(Part.LineSegment(FreeCAD.Vector(-26.0,0.0,-20.5), FreeCAD.Vector(-26.0,11.0,-20.5)).toShape())
groups.setdefault("chassis_rail", []).append(Part.LineSegment(FreeCAD.Vector(-26.0,11.0,-20.5), FreeCAD.Vector(-26.0,32.0,-20.5)).toShape())
groups.setdefault("chassis_rail", []).append(Part.LineSegment(FreeCAD.Vector(-26.0,32.0,-20.5), FreeCAD.Vector(-26.0,48.0,-20.5)).toShape())
groups.setdefault("chassis_rail", []).append(Part.LineSegment(FreeCAD.Vector(-26.0,48.0,-20.5), FreeCAD.Vector(-26.0,64.0,-20.5)).toShape())
groups.setdefault("chassis_rail", []).append(Part.LineSegment(FreeCAD.Vector(-26.0,64.0,-20.5), FreeCAD.Vector(-26.0,83.0,-20.5)).toShape())
groups.setdefault("chassis_rail", []).append(Part.LineSegment(FreeCAD.Vector(-26.0,83.0,-20.5), FreeCAD.Vector(-26.0,96.0,-20.5)).toShape())
groups.setdefault("deck_lo_edge", []).append(Part.LineSegment(FreeCAD.Vector(-48.0,0.0,0.0), FreeCAD.Vector(-48.0,24.0,0.0)).toShape())
groups.setdefault("deck_lo_edge", []).append(Part.LineSegment(FreeCAD.Vector(-48.0,24.0,0.0), FreeCAD.Vector(-48.0,32.0,0.0)).toShape())
groups.setdefault("deck_lo_edge", []).append(Part.LineSegment(FreeCAD.Vector(-48.0,32.0,0.0), FreeCAD.Vector(-48.0,48.0,0.0)).toShape())
groups.setdefault("deck_lo_edge", []).append(Part.LineSegment(FreeCAD.Vector(-48.0,48.0,0.0), FreeCAD.Vector(-48.0,64.0,0.0)).toShape())
groups.setdefault("deck_lo_edge", []).append(Part.LineSegment(FreeCAD.Vector(-48.0,64.0,0.0), FreeCAD.Vector(-48.0,72.0,0.0)).toShape())
groups.setdefault("deck_lo_edge", []).append(Part.LineSegment(FreeCAD.Vector(-48.0,72.0,0.0), FreeCAD.Vector(-48.0,96.0,0.0)).toShape())
groups.setdefault("chassis_rail", []).append(Part.LineSegment(FreeCAD.Vector(26.0,0.0,-20.5), FreeCAD.Vector(26.0,11.0,-20.5)).toShape())
groups.setdefault("chassis_rail", []).append(Part.LineSegment(FreeCAD.Vector(26.0,11.0,-20.5), FreeCAD.Vector(26.0,32.0,-20.5)).toShape())
groups.setdefault("chassis_rail", []).append(Part.LineSegment(FreeCAD.Vector(26.0,32.0,-20.5), FreeCAD.Vector(26.0,48.0,-20.5)).toShape())
groups.setdefault("chassis_rail", []).append(Part.LineSegment(FreeCAD.Vector(26.0,48.0,-20.5), FreeCAD.Vector(26.0,64.0,-20.5)).toShape())
groups.setdefault("chassis_rail", []).append(Part.LineSegment(FreeCAD.Vector(26.0,64.0,-20.5), FreeCAD.Vector(26.0,83.0,-20.5)).toShape())
groups.setdefault("chassis_rail", []).append(Part.LineSegment(FreeCAD.Vector(26.0,83.0,-20.5), FreeCAD.Vector(26.0,96.0,-20.5)).toShape())
groups.setdefault("deck_lo_edge", []).append(Part.LineSegment(FreeCAD.Vector(48.0,0.0,0.0), FreeCAD.Vector(48.0,24.0,0.0)).toShape())
groups.setdefault("deck_lo_edge", []).append(Part.LineSegment(FreeCAD.Vector(48.0,24.0,0.0), FreeCAD.Vector(48.0,32.0,0.0)).toShape())
groups.setdefault("deck_lo_edge", []).append(Part.LineSegment(FreeCAD.Vector(48.0,32.0,0.0), FreeCAD.Vector(48.0,48.0,0.0)).toShape())
groups.setdefault("deck_lo_edge", []).append(Part.LineSegment(FreeCAD.Vector(48.0,48.0,0.0), FreeCAD.Vector(48.0,64.0,0.0)).toShape())
groups.setdefault("deck_lo_edge", []).append(Part.LineSegment(FreeCAD.Vector(48.0,64.0,0.0), FreeCAD.Vector(48.0,72.0,0.0)).toShape())
groups.setdefault("deck_lo_edge", []).append(Part.LineSegment(FreeCAD.Vector(48.0,72.0,0.0), FreeCAD.Vector(48.0,96.0,0.0)).toShape())
groups.setdefault("chassis_cross", []).append(Part.LineSegment(FreeCAD.Vector(-26.0,0.0,-20.5), FreeCAD.Vector(0.0,0.0,-20.5)).toShape())
groups.setdefault("chassis_cross", []).append(Part.LineSegment(FreeCAD.Vector(0.0,0.0,-20.5), FreeCAD.Vector(26.0,0.0,-20.5)).toShape())
groups.setdefault("chassis_cross", []).append(Part.LineSegment(FreeCAD.Vector(-26.0,32.0,-20.5), FreeCAD.Vector(0.0,32.0,-20.5)).toShape())
groups.setdefault("chassis_cross", []).append(Part.LineSegment(FreeCAD.Vector(0.0,32.0,-20.5), FreeCAD.Vector(26.0,32.0,-20.5)).toShape())
groups.setdefault("chassis_cross", []).append(Part.LineSegment(FreeCAD.Vector(-26.0,64.0,-20.5), FreeCAD.Vector(0.0,64.0,-20.5)).toShape())
groups.setdefault("chassis_cross", []).append(Part.LineSegment(FreeCAD.Vector(0.0,64.0,-20.5), FreeCAD.Vector(26.0,64.0,-20.5)).toShape())
groups.setdefault("chassis_cross", []).append(Part.LineSegment(FreeCAD.Vector(-26.0,96.0,-20.5), FreeCAD.Vector(0.0,96.0,-20.5)).toShape())
groups.setdefault("chassis_cross", []).append(Part.LineSegment(FreeCAD.Vector(0.0,96.0,-20.5), FreeCAD.Vector(26.0,96.0,-20.5)).toShape())
groups.setdefault("deck_lo_beam", []).append(Part.LineSegment(FreeCAD.Vector(-48.0,0.0,0.0), FreeCAD.Vector(-15.0,0.0,0.0)).toShape())
groups.setdefault("deck_lo_beam", []).append(Part.LineSegment(FreeCAD.Vector(-15.0,0.0,0.0), FreeCAD.Vector(0.0,0.0,0.0)).toShape())
groups.setdefault("deck_lo_beam", []).append(Part.LineSegment(FreeCAD.Vector(0.0,0.0,0.0), FreeCAD.Vector(15.0,0.0,0.0)).toShape())
groups.setdefault("deck_lo_beam", []).append(Part.LineSegment(FreeCAD.Vector(15.0,0.0,0.0), FreeCAD.Vector(48.0,0.0,0.0)).toShape())
groups.setdefault("skirt_stub", []).append(Part.LineSegment(FreeCAD.Vector(-26.0,0.0,-20.5), FreeCAD.Vector(-48.0,0.0,0.0)).toShape())
groups.setdefault("skirt_stub", []).append(Part.LineSegment(FreeCAD.Vector(26.0,0.0,-20.5), FreeCAD.Vector(48.0,0.0,0.0)).toShape())
groups.setdefault("vbrace_lo", []).append(Part.LineSegment(FreeCAD.Vector(-26.0,0.0,-20.5), FreeCAD.Vector(0.0,0.0,0.0)).toShape())
groups.setdefault("vbrace_lo", []).append(Part.LineSegment(FreeCAD.Vector(26.0,0.0,-20.5), FreeCAD.Vector(0.0,0.0,0.0)).toShape())
groups.setdefault("deck_lo_beam", []).append(Part.LineSegment(FreeCAD.Vector(-48.0,32.0,0.0), FreeCAD.Vector(0.0,32.0,0.0)).toShape())
groups.setdefault("deck_lo_beam", []).append(Part.LineSegment(FreeCAD.Vector(0.0,32.0,0.0), FreeCAD.Vector(48.0,32.0,0.0)).toShape())
groups.setdefault("skirt_stub", []).append(Part.LineSegment(FreeCAD.Vector(-26.0,32.0,-20.5), FreeCAD.Vector(-48.0,32.0,0.0)).toShape())
groups.setdefault("skirt_stub", []).append(Part.LineSegment(FreeCAD.Vector(26.0,32.0,-20.5), FreeCAD.Vector(48.0,32.0,0.0)).toShape())
groups.setdefault("vbrace_lo", []).append(Part.LineSegment(FreeCAD.Vector(-26.0,32.0,-20.5), FreeCAD.Vector(0.0,32.0,0.0)).toShape())
groups.setdefault("vbrace_lo", []).append(Part.LineSegment(FreeCAD.Vector(26.0,32.0,-20.5), FreeCAD.Vector(0.0,32.0,0.0)).toShape())
groups.setdefault("deck_lo_beam", []).append(Part.LineSegment(FreeCAD.Vector(-48.0,64.0,0.0), FreeCAD.Vector(0.0,64.0,0.0)).toShape())
groups.setdefault("deck_lo_beam", []).append(Part.LineSegment(FreeCAD.Vector(0.0,64.0,0.0), FreeCAD.Vector(48.0,64.0,0.0)).toShape())
groups.setdefault("skirt_stub", []).append(Part.LineSegment(FreeCAD.Vector(-26.0,64.0,-20.5), FreeCAD.Vector(-48.0,64.0,0.0)).toShape())
groups.setdefault("skirt_stub", []).append(Part.LineSegment(FreeCAD.Vector(26.0,64.0,-20.5), FreeCAD.Vector(48.0,64.0,0.0)).toShape())
groups.setdefault("vbrace_lo", []).append(Part.LineSegment(FreeCAD.Vector(-26.0,64.0,-20.5), FreeCAD.Vector(0.0,64.0,0.0)).toShape())
groups.setdefault("vbrace_lo", []).append(Part.LineSegment(FreeCAD.Vector(26.0,64.0,-20.5), FreeCAD.Vector(0.0,64.0,0.0)).toShape())
groups.setdefault("deck_lo_beam", []).append(Part.LineSegment(FreeCAD.Vector(-48.0,96.0,0.0), FreeCAD.Vector(0.0,96.0,0.0)).toShape())
groups.setdefault("deck_lo_beam", []).append(Part.LineSegment(FreeCAD.Vector(0.0,96.0,0.0), FreeCAD.Vector(48.0,96.0,0.0)).toShape())
groups.setdefault("skirt_stub", []).append(Part.LineSegment(FreeCAD.Vector(-26.0,96.0,-20.5), FreeCAD.Vector(-48.0,96.0,0.0)).toShape())
groups.setdefault("skirt_stub", []).append(Part.LineSegment(FreeCAD.Vector(26.0,96.0,-20.5), FreeCAD.Vector(48.0,96.0,0.0)).toShape())
groups.setdefault("vbrace_lo", []).append(Part.LineSegment(FreeCAD.Vector(-26.0,96.0,-20.5), FreeCAD.Vector(0.0,96.0,0.0)).toShape())
groups.setdefault("vbrace_lo", []).append(Part.LineSegment(FreeCAD.Vector(26.0,96.0,-20.5), FreeCAD.Vector(0.0,96.0,0.0)).toShape())
groups.setdefault("deck_spine", []).append(Part.LineSegment(FreeCAD.Vector(0.0,0.0,0.0), FreeCAD.Vector(0.0,32.0,0.0)).toShape())
groups.setdefault("deck_spine", []).append(Part.LineSegment(FreeCAD.Vector(0.0,32.0,0.0), FreeCAD.Vector(0.0,48.0,0.0)).toShape())
groups.setdefault("deck_spine", []).append(Part.LineSegment(FreeCAD.Vector(0.0,48.0,0.0), FreeCAD.Vector(0.0,64.0,0.0)).toShape())
groups.setdefault("deck_spine", []).append(Part.LineSegment(FreeCAD.Vector(0.0,64.0,0.0), FreeCAD.Vector(0.0,96.0,0.0)).toShape())
groups.setdefault("post", []).append(Part.LineSegment(FreeCAD.Vector(-48.0,0.0,0.0), FreeCAD.Vector(-48.0,0.0,55.0)).toShape())
groups.setdefault("post", []).append(Part.LineSegment(FreeCAD.Vector(48.0,0.0,0.0), FreeCAD.Vector(48.0,0.0,55.0)).toShape())
groups.setdefault("post", []).append(Part.LineSegment(FreeCAD.Vector(-48.0,48.0,0.0), FreeCAD.Vector(-48.0,48.0,55.0)).toShape())
groups.setdefault("post", []).append(Part.LineSegment(FreeCAD.Vector(48.0,48.0,0.0), FreeCAD.Vector(48.0,48.0,55.0)).toShape())
groups.setdefault("post", []).append(Part.LineSegment(FreeCAD.Vector(-48.0,96.0,0.0), FreeCAD.Vector(-48.0,96.0,55.0)).toShape())
groups.setdefault("post", []).append(Part.LineSegment(FreeCAD.Vector(48.0,96.0,0.0), FreeCAD.Vector(48.0,96.0,55.0)).toShape())
groups.setdefault("deck_hi_end", []).append(Part.LineSegment(FreeCAD.Vector(-48.0,0.0,55.0), FreeCAD.Vector(-26.0,0.0,55.0)).toShape())
groups.setdefault("deck_hi_end", []).append(Part.LineSegment(FreeCAD.Vector(-26.0,0.0,55.0), FreeCAD.Vector(-15.0,0.0,55.0)).toShape())
groups.setdefault("deck_hi_end", []).append(Part.LineSegment(FreeCAD.Vector(-15.0,0.0,55.0), FreeCAD.Vector(0.0,0.0,55.0)).toShape())
groups.setdefault("deck_hi_end", []).append(Part.LineSegment(FreeCAD.Vector(0.0,0.0,55.0), FreeCAD.Vector(15.0,0.0,55.0)).toShape())
groups.setdefault("deck_hi_end", []).append(Part.LineSegment(FreeCAD.Vector(15.0,0.0,55.0), FreeCAD.Vector(26.0,0.0,55.0)).toShape())
groups.setdefault("deck_hi_end", []).append(Part.LineSegment(FreeCAD.Vector(26.0,0.0,55.0), FreeCAD.Vector(48.0,0.0,55.0)).toShape())
groups.setdefault("door_jamb", []).append(Part.LineSegment(FreeCAD.Vector(-15.0,0.0,0.0), FreeCAD.Vector(-15.0,0.0,55.0)).toShape())
groups.setdefault("door_jamb", []).append(Part.LineSegment(FreeCAD.Vector(15.0,0.0,0.0), FreeCAD.Vector(15.0,0.0,55.0)).toShape())
groups.setdefault("deck_hi_cross", []).append(Part.LineSegment(FreeCAD.Vector(-48.0,32.0,55.0), FreeCAD.Vector(-26.0,32.0,55.0)).toShape())
groups.setdefault("deck_hi_cross", []).append(Part.LineSegment(FreeCAD.Vector(-26.0,32.0,55.0), FreeCAD.Vector(-24.0,32.0,55.0)).toShape())
groups.setdefault("deck_hi_cross", []).append(Part.LineSegment(FreeCAD.Vector(-24.0,32.0,55.0), FreeCAD.Vector(0.0,32.0,55.0)).toShape())
groups.setdefault("deck_hi_cross", []).append(Part.LineSegment(FreeCAD.Vector(0.0,32.0,55.0), FreeCAD.Vector(24.0,32.0,55.0)).toShape())
groups.setdefault("deck_hi_cross", []).append(Part.LineSegment(FreeCAD.Vector(24.0,32.0,55.0), FreeCAD.Vector(26.0,32.0,55.0)).toShape())
groups.setdefault("deck_hi_cross", []).append(Part.LineSegment(FreeCAD.Vector(26.0,32.0,55.0), FreeCAD.Vector(48.0,32.0,55.0)).toShape())
groups.setdefault("deck_hi_cross", []).append(Part.LineSegment(FreeCAD.Vector(-48.0,64.0,55.0), FreeCAD.Vector(-26.0,64.0,55.0)).toShape())
groups.setdefault("deck_hi_cross", []).append(Part.LineSegment(FreeCAD.Vector(-26.0,64.0,55.0), FreeCAD.Vector(-12.0,64.0,55.0)).toShape())
groups.setdefault("deck_hi_cross", []).append(Part.LineSegment(FreeCAD.Vector(-12.0,64.0,55.0), FreeCAD.Vector(0.0,64.0,55.0)).toShape())
groups.setdefault("deck_hi_cross", []).append(Part.LineSegment(FreeCAD.Vector(0.0,64.0,55.0), FreeCAD.Vector(12.0,64.0,55.0)).toShape())
groups.setdefault("deck_hi_cross", []).append(Part.LineSegment(FreeCAD.Vector(12.0,64.0,55.0), FreeCAD.Vector(26.0,64.0,55.0)).toShape())
groups.setdefault("deck_hi_cross", []).append(Part.LineSegment(FreeCAD.Vector(26.0,64.0,55.0), FreeCAD.Vector(48.0,64.0,55.0)).toShape())
groups.setdefault("deck_hi_end", []).append(Part.LineSegment(FreeCAD.Vector(-48.0,96.0,55.0), FreeCAD.Vector(-26.0,96.0,55.0)).toShape())
groups.setdefault("deck_hi_end", []).append(Part.LineSegment(FreeCAD.Vector(-26.0,96.0,55.0), FreeCAD.Vector(-7.0,96.0,55.0)).toShape())
groups.setdefault("deck_hi_end", []).append(Part.LineSegment(FreeCAD.Vector(-7.0,96.0,55.0), FreeCAD.Vector(0.0,96.0,55.0)).toShape())
groups.setdefault("deck_hi_end", []).append(Part.LineSegment(FreeCAD.Vector(0.0,96.0,55.0), FreeCAD.Vector(7.0,96.0,55.0)).toShape())
groups.setdefault("deck_hi_end", []).append(Part.LineSegment(FreeCAD.Vector(7.0,96.0,55.0), FreeCAD.Vector(26.0,96.0,55.0)).toShape())
groups.setdefault("deck_hi_end", []).append(Part.LineSegment(FreeCAD.Vector(26.0,96.0,55.0), FreeCAD.Vector(48.0,96.0,55.0)).toShape())
groups.setdefault("xbrace_end", []).append(Part.LineSegment(FreeCAD.Vector(-48.0,96.0,0.0), FreeCAD.Vector(0.0,96.0,48.0)).toShape())
groups.setdefault("xbrace_end", []).append(Part.LineSegment(FreeCAD.Vector(0.0,96.0,48.0), FreeCAD.Vector(7.0,96.0,55.0)).toShape())
groups.setdefault("xbrace_end", []).append(Part.LineSegment(FreeCAD.Vector(48.0,96.0,0.0), FreeCAD.Vector(0.0,96.0,48.0)).toShape())
groups.setdefault("xbrace_end", []).append(Part.LineSegment(FreeCAD.Vector(0.0,96.0,48.0), FreeCAD.Vector(-7.0,96.0,55.0)).toShape())
groups.setdefault("deck_hi_rail", []).append(Part.LineSegment(FreeCAD.Vector(-48.0,0.0,55.0), FreeCAD.Vector(-48.0,24.0,55.0)).toShape())
groups.setdefault("deck_hi_rail", []).append(Part.LineSegment(FreeCAD.Vector(-48.0,24.0,55.0), FreeCAD.Vector(-48.0,32.0,55.0)).toShape())
groups.setdefault("deck_hi_rail", []).append(Part.LineSegment(FreeCAD.Vector(-48.0,32.0,55.0), FreeCAD.Vector(-48.0,48.0,55.0)).toShape())
groups.setdefault("deck_hi_rail", []).append(Part.LineSegment(FreeCAD.Vector(-48.0,48.0,55.0), FreeCAD.Vector(-48.0,64.0,55.0)).toShape())
groups.setdefault("deck_hi_rail", []).append(Part.LineSegment(FreeCAD.Vector(-48.0,64.0,55.0), FreeCAD.Vector(-48.0,72.0,55.0)).toShape())
groups.setdefault("deck_hi_rail", []).append(Part.LineSegment(FreeCAD.Vector(-48.0,72.0,55.0), FreeCAD.Vector(-48.0,96.0,55.0)).toShape())
groups.setdefault("joist_hi", []).append(Part.LineSegment(FreeCAD.Vector(-24.0,32.0,55.0), FreeCAD.Vector(-24.0,64.0,55.0)).toShape())
groups.setdefault("deck_hi_rail", []).append(Part.LineSegment(FreeCAD.Vector(48.0,0.0,55.0), FreeCAD.Vector(48.0,24.0,55.0)).toShape())
groups.setdefault("deck_hi_rail", []).append(Part.LineSegment(FreeCAD.Vector(48.0,24.0,55.0), FreeCAD.Vector(48.0,32.0,55.0)).toShape())
groups.setdefault("deck_hi_rail", []).append(Part.LineSegment(FreeCAD.Vector(48.0,32.0,55.0), FreeCAD.Vector(48.0,48.0,55.0)).toShape())
groups.setdefault("deck_hi_rail", []).append(Part.LineSegment(FreeCAD.Vector(48.0,48.0,55.0), FreeCAD.Vector(48.0,64.0,55.0)).toShape())
groups.setdefault("deck_hi_rail", []).append(Part.LineSegment(FreeCAD.Vector(48.0,64.0,55.0), FreeCAD.Vector(48.0,72.0,55.0)).toShape())
groups.setdefault("deck_hi_rail", []).append(Part.LineSegment(FreeCAD.Vector(48.0,72.0,55.0), FreeCAD.Vector(48.0,96.0,55.0)).toShape())
groups.setdefault("joist_hi", []).append(Part.LineSegment(FreeCAD.Vector(24.0,32.0,55.0), FreeCAD.Vector(24.0,64.0,55.0)).toShape())
groups.setdefault("long_brace", []).append(Part.LineSegment(FreeCAD.Vector(-48.0,96.0,0.0), FreeCAD.Vector(-12.0,64.0,55.0)).toShape())
groups.setdefault("long_brace", []).append(Part.LineSegment(FreeCAD.Vector(-48.0,0.0,0.0), FreeCAD.Vector(-24.0,32.0,55.0)).toShape())
groups.setdefault("long_brace", []).append(Part.LineSegment(FreeCAD.Vector(48.0,96.0,0.0), FreeCAD.Vector(12.0,64.0,55.0)).toShape())
groups.setdefault("long_brace", []).append(Part.LineSegment(FreeCAD.Vector(48.0,0.0,0.0), FreeCAD.Vector(24.0,32.0,55.0)).toShape())
groups.setdefault("chamfer_hi", []).append(Part.LineSegment(FreeCAD.Vector(-48.0,0.0,55.0), FreeCAD.Vector(-27.5,0.0,75.5)).toShape())
groups.setdefault("chamfer_hi", []).append(Part.LineSegment(FreeCAD.Vector(48.0,0.0,55.0), FreeCAD.Vector(27.5,0.0,75.5)).toShape())
groups.setdefault("rim_cross", []).append(Part.LineSegment(FreeCAD.Vector(-27.5,0.0,75.5), FreeCAD.Vector(27.5,0.0,75.5)).toShape())
groups.setdefault("chamfer_hi", []).append(Part.LineSegment(FreeCAD.Vector(-48.0,24.0,55.0), FreeCAD.Vector(-27.5,24.0,75.5)).toShape())
groups.setdefault("chamfer_hi", []).append(Part.LineSegment(FreeCAD.Vector(48.0,24.0,55.0), FreeCAD.Vector(27.5,24.0,75.5)).toShape())
groups.setdefault("chamfer_hi", []).append(Part.LineSegment(FreeCAD.Vector(-48.0,72.0,55.0), FreeCAD.Vector(-27.5,72.0,75.5)).toShape())
groups.setdefault("chamfer_hi", []).append(Part.LineSegment(FreeCAD.Vector(48.0,72.0,55.0), FreeCAD.Vector(27.5,72.0,75.5)).toShape())
groups.setdefault("chamfer_hi", []).append(Part.LineSegment(FreeCAD.Vector(-48.0,96.0,55.0), FreeCAD.Vector(-27.5,96.0,75.5)).toShape())
groups.setdefault("chamfer_hi", []).append(Part.LineSegment(FreeCAD.Vector(48.0,96.0,55.0), FreeCAD.Vector(27.5,96.0,75.5)).toShape())
groups.setdefault("rim_cross", []).append(Part.LineSegment(FreeCAD.Vector(-27.5,96.0,75.5), FreeCAD.Vector(27.5,96.0,75.5)).toShape())
groups.setdefault("rim_stringer", []).append(Part.LineSegment(FreeCAD.Vector(-27.5,0.0,75.5), FreeCAD.Vector(-27.5,24.0,75.5)).toShape())
groups.setdefault("rim_stringer", []).append(Part.LineSegment(FreeCAD.Vector(-27.5,24.0,75.5), FreeCAD.Vector(-27.5,72.0,75.5)).toShape())
groups.setdefault("rim_stringer", []).append(Part.LineSegment(FreeCAD.Vector(-27.5,72.0,75.5), FreeCAD.Vector(-27.5,96.0,75.5)).toShape())
groups.setdefault("rim_stringer", []).append(Part.LineSegment(FreeCAD.Vector(27.5,0.0,75.5), FreeCAD.Vector(27.5,24.0,75.5)).toShape())
groups.setdefault("rim_stringer", []).append(Part.LineSegment(FreeCAD.Vector(27.5,24.0,75.5), FreeCAD.Vector(27.5,72.0,75.5)).toShape())
groups.setdefault("rim_stringer", []).append(Part.LineSegment(FreeCAD.Vector(27.5,72.0,75.5), FreeCAD.Vector(27.5,96.0,75.5)).toShape())
groups.setdefault("nose_rim", []).append(Part.LineSegment(FreeCAD.Vector(-15.0,132.0,18.5), FreeCAD.Vector(15.0,132.0,18.5)).toShape())
groups.setdefault("nose_rim", []).append(Part.LineSegment(FreeCAD.Vector(15.0,132.0,18.5), FreeCAD.Vector(15.0,132.0,36.5)).toShape())
groups.setdefault("nose_rim", []).append(Part.LineSegment(FreeCAD.Vector(15.0,132.0,36.5), FreeCAD.Vector(-15.0,132.0,36.5)).toShape())
groups.setdefault("nose_rim", []).append(Part.LineSegment(FreeCAD.Vector(-15.0,132.0,36.5), FreeCAD.Vector(-15.0,132.0,18.5)).toShape())
groups.setdefault("nose_stringer", []).append(Part.LineSegment(FreeCAD.Vector(-26.0,96.0,-20.5), FreeCAD.Vector(-15.0,132.0,18.5)).toShape())
groups.setdefault("nose_stringer", []).append(Part.LineSegment(FreeCAD.Vector(26.0,96.0,-20.5), FreeCAD.Vector(15.0,132.0,18.5)).toShape())
groups.setdefault("nose_stringer", []).append(Part.LineSegment(FreeCAD.Vector(48.0,96.0,0.0), FreeCAD.Vector(15.0,132.0,18.5)).toShape())
groups.setdefault("nose_stringer", []).append(Part.LineSegment(FreeCAD.Vector(48.0,96.0,55.0), FreeCAD.Vector(15.0,132.0,36.5)).toShape())
groups.setdefault("nose_stringer", []).append(Part.LineSegment(FreeCAD.Vector(27.5,96.0,75.5), FreeCAD.Vector(15.0,132.0,36.5)).toShape())
groups.setdefault("nose_stringer", []).append(Part.LineSegment(FreeCAD.Vector(-27.5,96.0,75.5), FreeCAD.Vector(-15.0,132.0,36.5)).toShape())
groups.setdefault("nose_stringer", []).append(Part.LineSegment(FreeCAD.Vector(-48.0,96.0,55.0), FreeCAD.Vector(-15.0,132.0,36.5)).toShape())
groups.setdefault("nose_stringer", []).append(Part.LineSegment(FreeCAD.Vector(-48.0,96.0,0.0), FreeCAD.Vector(-15.0,132.0,18.5)).toShape())
groups.setdefault("tail_rim", []).append(Part.LineSegment(FreeCAD.Vector(-27.5,-20.5,0.0), FreeCAD.Vector(27.5,-20.5,0.0)).toShape())
groups.setdefault("tail_rim", []).append(Part.LineSegment(FreeCAD.Vector(27.5,-20.5,0.0), FreeCAD.Vector(27.5,-20.5,55.0)).toShape())
groups.setdefault("tail_rim", []).append(Part.LineSegment(FreeCAD.Vector(27.5,-20.5,55.0), FreeCAD.Vector(-27.5,-20.5,55.0)).toShape())
groups.setdefault("tail_rim", []).append(Part.LineSegment(FreeCAD.Vector(-27.5,-20.5,55.0), FreeCAD.Vector(-27.5,-20.5,0.0)).toShape())
groups.setdefault("tail_stringer", []).append(Part.LineSegment(FreeCAD.Vector(-26.0,0.0,-20.5), FreeCAD.Vector(-27.5,-20.5,0.0)).toShape())
groups.setdefault("tail_stringer", []).append(Part.LineSegment(FreeCAD.Vector(26.0,0.0,-20.5), FreeCAD.Vector(27.5,-20.5,0.0)).toShape())
groups.setdefault("tail_stringer", []).append(Part.LineSegment(FreeCAD.Vector(48.0,0.0,0.0), FreeCAD.Vector(27.5,-20.5,0.0)).toShape())
groups.setdefault("tail_stringer", []).append(Part.LineSegment(FreeCAD.Vector(48.0,0.0,55.0), FreeCAD.Vector(27.5,-20.5,55.0)).toShape())
groups.setdefault("tail_stringer", []).append(Part.LineSegment(FreeCAD.Vector(27.5,0.0,75.5), FreeCAD.Vector(27.5,-20.5,55.0)).toShape())
groups.setdefault("tail_stringer", []).append(Part.LineSegment(FreeCAD.Vector(-27.5,0.0,75.5), FreeCAD.Vector(-27.5,-20.5,55.0)).toShape())
groups.setdefault("tail_stringer", []).append(Part.LineSegment(FreeCAD.Vector(-48.0,0.0,55.0), FreeCAD.Vector(-27.5,-20.5,55.0)).toShape())
groups.setdefault("tail_stringer", []).append(Part.LineSegment(FreeCAD.Vector(-48.0,0.0,0.0), FreeCAD.Vector(-27.5,-20.5,0.0)).toShape())
allshapes = []
for g, shapes in groups.items():
    obj = doc.addObject("Part::Feature", g)
    obj.Shape = Part.makeCompound(shapes)
    allshapes += shapes
frame = doc.addObject("Part::Feature", "Frame_all_members")
frame.Shape = Part.makeCompound(allshapes)
doc.recompute()
FreeCAD.Console.PrintMessage("Float frame v2 imported: %d members (inches)\n" % len(allshapes))
